GIP-BLACK-MIB DEFINITIONS ::= BEGIN
IMPORTS
	xyna FROM GIP-XYNA-MIB;

------------------------------------------------------
-- Copyright 2022 Xyna GmbH, Germany
--
-- Licensed under the Apache License, Version 2.0 (the "License");
-- you may not use this file except in compliance with the License.
-- You may obtain a copy of the License at
--
--  http://www.apache.org/licenses/LICENSE-2.0
--
-- Unless required by applicable law or agreed to in writing, software
-- distributed under the License is distributed on an "AS IS" BASIS,
-- WITHOUT WARRANTIES OR CONDITIONS OF ANY KIND, either express or implied.
-- See the License for the specific language governing permissions and
-- limitations under the License.
------------------------------------------------------
--
black MODULE-IDENTITY
        LAST-UPDATED "201204030832Z"    -- Apr 03, 2012 8:32:00 AM
        ORGANIZATION "Xyna GmbH"
        CONTACT-INFO "Xyna GmbH"
        DESCRIPTION  ""
        REVISION     "201204030832Z"    -- Apr 03, 2012 8:32:00 AM
        DESCRIPTION  ""
	::= { xyna 11 }



-- Departments

xprc OBJECT IDENTIFIER
	::= { black 1 }

xfwh OBJECT IDENTIFIER
	::= { black 2 }

xdev OBJECT IDENTIFIER
	::= { black 3 }
	
xfmg OBJECT IDENTIFIER
	::= { black 4 }

xact OBJECT IDENTIFIER
	::= { black 9 }

xmcp OBJECT IDENTIFIER
	::= { black 10 }

END
