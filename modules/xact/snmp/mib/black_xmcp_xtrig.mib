GIP-BLACK-XMCP-XTRIG-MIB DEFINITIONS ::= BEGIN
IMPORTS
	xmcp FROM GIP-BLACK-MIB;

------------------------------------------------------
-- Copyright 2022 Xyna GmbH, Germany
--
-- Licensed under the Apache License, Version 2.0 (the "License");
-- you may not use this file except in compliance with the License.
-- You may obtain a copy of the License at
--
--  http://www.apache.org/licenses/LICENSE-2.0
--
-- Unless required by applicable law or agreed to in writing, software
-- distributed under the License is distributed on an "AS IS" BASIS,
-- WITHOUT WARRANTIES OR CONDITIONS OF ANY KIND, either express or implied.
-- See the License for the specific language governing permissions and
-- limitations under the License.
------------------------------------------------------
--
xTrig MODULE-IDENTITY
        LAST-UPDATED "201204030832Z"    -- Apr 03, 2012 8:32:00 AM
        ORGANIZATION "Xyna GmbH"
        CONTACT-INFO "Xyna GmbH"
        DESCRIPTION  ""
        REVISION     "201204030832Z"    -- Apr 03, 2012 8:32:00 AM
        DESCRIPTION  ""
	::= { xmcp 1 }


impls OBJECT IDENTIFIER
	::= { xTrig 1 }


-- ##########################################################################


oracleAQTable OBJECT-TYPE
    SYNTAX  SEQUENCE OF OracleAQEntry
    MAX-ACCESS not-accessible
    STATUS  current
    DESCRIPTION
        "Table of Oracle AQ trigger instances."
    ::= { impls 1 }


oracleAQEntry OBJECT-TYPE
        SYNTAX  OracleAQEntry
        MAX-ACCESS not-accessible
        STATUS  current
        DESCRIPTION
                "Entry for an Oracle AQ trigger instance."
        INDEX {
                orderType
        }
        ::= { oracleAQTable 1 }


OracleAQEntry ::= SEQUENCE {
		instanceName				OCTET STRING,
		queueName					OCTET STRING,
        processedOverall			Gauge,
		activeConnections			Gauge,
        lastDequeueTime          	OCTET STRING }


instanceName OBJECT-TYPE
        SYNTAX  OCTET STRING
        MAX-ACCESS read-only
        STATUS  current
        DESCRIPTION
                "Name of the Oracle AQ trigger instance."
        ::= { oracleAQEntry 1 }

queueName OBJECT-TYPE
        SYNTAX  OCTET STRING
        MAX-ACCESS read-only
        STATUS  current
        DESCRIPTION
                "Name of the internal queue the trigger instance is listening on."
        ::= { oracleAQEntry 2 }
		

processedOverall OBJECT-TYPE
        SYNTAX  Gauge
        MAX-ACCESS read-only
        STATUS  current
        DESCRIPTION
                "Count of all processed JMS messages."
        ::= { oracleAQEntry 3 }


activeConnections OBJECT-TYPE
        SYNTAX  Gauge
        MAX-ACCESS read-only
        STATUS  current
        DESCRIPTION
                "Count of currently active connections."
        ::= { oracleAQEntry 4 }


lastDequeueTime OBJECT-TYPE
        SYNTAX  OCTET STRING
        MAX-ACCESS read-only
        STATUS  current
        DESCRIPTION
                "Returns the ISO-Timestamp of the last dequeue time."
        ::= { oracleAQEntry 5 }


END
